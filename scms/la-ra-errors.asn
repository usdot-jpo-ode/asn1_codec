-- 
--  Copyright 2017 Crash Avoidance Metrics Partner, VSC5 Consortium
-- 
--  Licensed under the Apache License, Version 2.0 (the "License");
--  you may not use this file except in compliance with the License.
--  You may obtain a copy of the License at
-- 
--     http://www.apache.org/licenses/LICENSE-2.0
-- 
--  Unless required by applicable law or agreed to in writing, software
--  distributed under the License is distributed on an "AS IS" BASIS,
--  WITHOUT WARRANTIES OR CONDITIONS OF ANY KIND, either express or implied.
--  See the License for the specific language governing permissions and
--  limitations under the License.
-- 

Ieee1609Dot2LaRaError
{iso(1) identified-organization(3) ieee(111) 
standards-association-numbered-series-standards(2) wave-stds(1609)  
dot2(2) scms(2) errors(2) la-ra(11)}

DEFINITIONS AUTOMATIC TAGS ::= BEGIN

EXPORTS ALL;

LaRaError ::= CHOICE {
	la-ra	LaRaErrorCode,
	...
}

LaRaErrorCode ::= ENUMERATED {
  invalidPcaKey,        -- no valid key for encryption to PCA available
  invalidIMin,          -- iMin is invalid
  invalidIMax,          -- iMax is invalid
  invalidContinueChain, -- continue chain is neither 0 nor 1
  invalidLinkagechainId,-- linkagechainId is invalid
  invalidJMax,          -- invalid jMax value (e.g. too large)
  ...
}


END
