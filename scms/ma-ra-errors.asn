-- 
--  Copyright 2017 Crash Avoidance Metrics Partner, VSC5 Consortium
-- 
--  Licensed under the Apache License, Version 2.0 (the "License");
--  you may not use this file except in compliance with the License.
--  You may obtain a copy of the License at
-- 
--     http://www.apache.org/licenses/LICENSE-2.0
-- 
--  Unless required by applicable law or agreed to in writing, software
--  distributed under the License is distributed on an "AS IS" BASIS,
--  WITHOUT WARRANTIES OR CONDITIONS OF ANY KIND, either express or implied.
--  See the License for the specific language governing permissions and
--  limitations under the License.
-- 

Ieee1609Dot2MaRaError
{iso(1) identified-organization(3) ieee(111) 
standards-association-numbered-series-standards(2) wave-stds(1609)  
dot2(2) scms(2) errors(2) ma-ra(14)}

DEFINITIONS AUTOMATIC TAGS ::= BEGIN

EXPORTS ALL;


MaRaError ::= CHOICE {
  ma-ra-base-error          MaRaBaseErrorCode,
  ma-ra-blacklist-error     MaRaBlacklistErrorCode,
  ma-ra-lci-error           MaRaLCIErrorCode,
  ma-ra-cdv-error           MaRaCDVErrorCode,    -- Added for RSE revocation
  ...
}

MaRaBaseErrorCode ::= ENUMERATED {
	raInternalTimeout,
        maRequestTimeout,
        raNoMaAuthorizationSignature, 
	raInvalidMaAuthorizationSignature,
        raInvalidInputValueFormat,
        raInvalidHashRequest,
        raInvalidRIFValue,
        raInvalidLinkageValue, 
	raNumberOfRequestsExceeded,
	noSecureConnectionToRequestor, -- not used yet
	hpcrIsUnknownToRA, -- not used yet
	...
}

MaRaBlacklistErrorCode ::= ENUMERATED {
	-- HPCR points to already blacklisted certificate
	alreadyBlacklisted,
	-- raCertificateAlreadyBlacklisted,
	...
}

MaRaLCIErrorCode ::= ENUMERATED {
	noLinkageChainIdentifiersKnownForHPCR, -- not used yet
	...
}

-- Added for RSE application and OBE identification cert revocation
MaRaCDVErrorCode ::= ENUMERATED {
    noCertificateDigestValuesKnownForRIF,
    ...
}
    
END
